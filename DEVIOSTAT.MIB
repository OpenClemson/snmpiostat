DEVIOSTAT-MIB DEFINITIONS ::= BEGIN

IMPORTS
    MODULE-IDENTITY, OBJECT-TYPE, Integer32, Counter32, experimental
	FROM SNMPv2-SMI
    DisplayString
	FROM SNMPv2-TC
;

devIOStatMIB MODULE-IDENTITY
    LAST-UPDATED	"201505260000Z"
    ORGANIZATION	"Clemson University"
    CONTACT-INFO	"email:	rschwa2@clemson.edu"
    DESCRIPTION		"Device IO data."
    REVISION		"201505260000Z"
    DESCRIPTION		"Initial release."
    ::= { experimental 2 }

devIOStatType ::= TEXTUAL-CONVENTION
    STATUS	current
    DESCRIPTION
	"A value that represents the device type, used by clients to decide
	 if the device stats should be displayed:

	 unknown(0)	Unknown device.
	 disk(1)	Disk.
	 partition(2)	Partition.
	 tape(3)	Tape drive."
    SYNTAX	INTEGER {
		    unknown(0),
		    disk(1),
		    partition(2),
		    tape(3)
		}

devIOStatTable OBJECT-TYPE
    SYNTAX	SEQUENCE OF DevIOStatEntry
    MAX-ACCESS	not-accessible
    STATUS	current
    DESCRIPTION
	"Table of device IO statistics."
    ::= { devIOStatMIB 1 }

devIOStatEntry OBJECT-TYPE
    SYNTAX	DevIOStatEntry
    MAX-ACCESS	not-accessible
    STATUS	current
    DESCRIPTION
	"An entry containing a device and its statistics."
    INDEX	{ devIOStatIndex }
    ::= { devIOStatTable 1 }

DevIOStatEntry ::= SEQUENCE {
  devIOStatIndex	Integer32,
  devIOStatDevice	DisplayString,
  devIOStatReads	Integer32,
  devIOStatReadMerges	Integer32,
  devIOStatReadSectors	DisplayString,
  devIOStatReadTicks	Integer32,
  devIOStatWrites	Integer32,
  devIOStatWriteMerges	Integer32,
  devIOStatWriteSectors	DisplayString,
  devIOStatWriteTicks	Integer32,
  devIOStatTicks	Integer32,
  devIOStatAveQ		Integer32,
  devIOStatType		devIOStatType
}

devIOStatIndex OBJECT-TYPE
    SYNTAX	Integer32 (0..65535)
    MAX-ACCESS	read-only
    STATUS	current
    DESCRIPTION
	"Reference index for each device."
    ::= { devIOStatEntry 1 }

devIOStatDevice OBJECT-TYPE
    SYNTAX	DisplayString
    MAX-ACCESS	read-only
    STATUS	current
    DESCRIPTION
	"The name of the device."
    ::= { devIOStatEntry 2 }

devIOStatReads OBJECT-TYPE
    SYNTAX	Integer32
    MAX-ACCESS	read-only
    STATUS	current
    DESCRIPTION
	"Number of reads from device."
    ::= { devIOStatEntry 3 }

devIOStatReadMerges OBJECT-TYPE
    SYNTAX	Integer32
    MAX-ACCESS	read-only
    STATUS	current
    DESCRIPTION
	"Number of reads merged for device."
    ::= { devIOStatEntry 4 }

devIOStatReadSectors OBJECT-TYPE
    SYNTAX	DisplayString
    MAX-ACCESS	read-only
    STATUS	current
    DESCRIPTION
	"Number of sectors read from device."
    ::= { devIOStatEntry 5 }

devIOStatReadTicks OBJECT-TYPE
    SYNTAX	Integer32
    MAX-ACCESS	read-only
    STATUS	current
    DESCRIPTION
	"Time spent reading from device (ms)."
    ::= { devIOStatEntry 6 }

devIOStatWrites OBJECT-TYPE
    SYNTAX	Integer32
    MAX-ACCESS	read-only
    STATUS	current
    DESCRIPTION
	"Number of writes to device."
    ::= { devIOStatEntry 7 }

devIOStatWriteMerges OBJECT-TYPE
    SYNTAX	Integer32
    MAX-ACCESS	read-only
    STATUS	current
    DESCRIPTION
	"Number of writes merged for device."
    ::= { devIOStatEntry 8 }

devIOStatWriteSectors OBJECT-TYPE
    SYNTAX	DisplayString
    MAX-ACCESS	read-only
    STATUS	current
    DESCRIPTION
	"Number of sectors written to device."
    ::= { devIOStatEntry 9 }

devIOStatWriteTicks OBJECT-TYPE
    SYNTAX	Integer32
    MAX-ACCESS	read-only
    STATUS	current
    DESCRIPTION
	"Time spent writing to device (ms)."
    ::= { devIOStatEntry 10 }

devIOStatTicks OBJECT-TYPE
    SYNTAX	Integer32
    MAX-ACCESS	read-only
    STATUS	current
    DESCRIPTION
	"Time spent doing IO (ms)."
    ::= { devIOStatEntry 11 }

devIOStatAveQ OBJECT-TYPE
    SYNTAX	Integer32
    MAX-ACCESS	read-only
    STATUS	current
    DESCRIPTION
	"Weighted time spent doing IO (ms)."
    ::= { devIOStatEntry 12 }

devIOStatType OBJECT-TYPE
    SYNTAX	devIOStatType
    MAX-ACCESS	read-only
    STATUS	current
    DESCRIPTION
	"Type of device."
    ::= { devIOStatEntry 13 }

END
